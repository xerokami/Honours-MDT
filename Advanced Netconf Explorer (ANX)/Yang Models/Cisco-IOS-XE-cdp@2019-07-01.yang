module Cisco-IOS-XE-cdp {
  namespace "http://cisco.com/ns/yang/Cisco-IOS-XE-cdp";
  prefix ios-cdp;

  import cisco-semver {
    prefix cisco-semver;
  }
  import Cisco-IOS-XE-native {
    prefix ios;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Native Cisco Discovery Protocol (CDP) Yang Model.
     Copyright (c) 2016-2017, 2019 by Cisco Systems, Inc.
     All rights reserved.";

  revision 2019-07-01 {
    description
      "- Establish semantic version baseline
       - Corrected behavior of cdp tlv under interface
       - Added support for BDI interface";
    cisco-semver:module-version "1.0.0";
  }
  revision 2019-01-22 {
    description
      "Added leaf for App-hosting Gigabit Ethernet interface";
  }
  revision 2017-11-27 {
    description
      "Added Change 25GE name";
  }
  revision 2017-11-14 {
    description
      "This revision has changes for new 40 and 100GE interface addition";
  }
  revision 2017-09-14 {
    description
      "This revision has changes for new 2gig interface addition";
  }
  revision 2017-08-16 {
    description
      "This revision has changes for new 5gig and 25gig interfaces addition";
  }
  revision 2017-02-07 {
    description
      "Initial revision";
  }

  grouping config-interface-cdp-grouping {
    container cdp {
      description
        "CDP interface subcommands";
      leaf enable {
        description
          "Enable CDP on interface";
        type boolean;
        default "false";
      }
      container tlv {
        description
          "Enable exchange of specific tlv information";
        when "../enable = 'true'";
        container app-config {
          description
            "Enable/Configure Application TLV";
          leaf app {
            description
              "Enable CDP location server on interface";
            type boolean;
            default "true";
          }
          leaf tlvtype {
            description
              "Configure APP TLV";
            type uint16 {
              range "1001..65535";
            }
          }
          leaf value {
            description
              "Configure App TLV Value information";
            type string;
          }
        }
        container app {
          status deprecated;
          description
            "Enable/Configure Application TLV";
          presence "true";
          leaf tlvtype {
            status deprecated;
            description
              "Configure APP TLV";
            type uint16 {
              range "1001..65535";
            }
          }
          leaf value {
            status deprecated;
            description
              "Configure App TLV Value information";
            type string;
          }
        }
        leaf server-location-config {
          description
            "Enable CDP location server on interface";
          type boolean;
          default "true";
        }
        leaf server-location {
          status deprecated;
          description
            "Enable CDP location server on interface";
          type empty;
        }
        leaf location-config {
          description
            "Exchange location information";
          type boolean;
          default "true";
        }
        leaf location {
          status deprecated;
          description
            "Exchange location information";
          type empty;
        }
      }
    }
  }

  grouping config-cdp-grouping {
    leaf holdtime {
      description
        "Specify the holdtime (in sec) to be sent in packets";
      type uint8 {
        range "10..255";
      }
    }
    leaf timer {
      description
        "Specify the rate at which CDP packets are sent (in sec)";
      type uint8 {
        range "5..254";
      }
    }
    leaf run {
      description
        "Enable CDP";
      type empty;
    }
  }

  augment "/ios:native/ios:cdp" {
    uses config-cdp-grouping;
  }
  augment "/ios:native/ios:interface/ios:BDI" {
    uses config-interface-cdp-grouping;
  }
  augment "/ios:native/ios:interface/ios:FastEthernet" {
    uses config-interface-cdp-grouping;
  }
  augment "/ios:native/ios:interface/ios:GigabitEthernet" {
    uses config-interface-cdp-grouping;
  }
  augment "/ios:native/ios:interface/ios:TenGigabitEthernet" {
    uses config-interface-cdp-grouping;
  }
  augment "/ios:native/ios:interface/ios:FiveGigabitEthernet" {
    uses config-interface-cdp-grouping;
  }
  augment "/ios:native/ios:interface/ios:AppGigabitEthernet" {
    uses config-interface-cdp-grouping;
  }
  augment "/ios:native/ios:interface/ios:TwentyFiveGigE" {
    uses config-interface-cdp-grouping;
  }
  augment "/ios:native/ios:interface/ios:TwoGigabitEthernet" {
    uses config-interface-cdp-grouping;
  }
  augment "/ios:native/ios:interface/ios:FortyGigabitEthernet" {
    uses config-interface-cdp-grouping;
  }
  augment "/ios:native/ios:interface/ios:HundredGigE" {
    uses config-interface-cdp-grouping;
  }
  augment "/ios:native/ios:interface/ios:Tunnel" {
    uses config-interface-cdp-grouping;
  }
  augment "/ios:native/ios:interface/ios:Virtual-Template" {
    uses config-interface-cdp-grouping;
  }
}
