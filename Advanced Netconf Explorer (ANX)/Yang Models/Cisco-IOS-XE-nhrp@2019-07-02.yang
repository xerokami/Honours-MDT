module Cisco-IOS-XE-nhrp {
  namespace "http://cisco.com/ns/yang/Cisco-IOS-XE-nhrp";
  prefix ios-nhrp;

  import cisco-semver {
    prefix cisco-semver;
  }
  import ietf-inet-types {
    prefix inet;
  }
  import Cisco-IOS-XE-interface-common {
    prefix ios-ifc;
  }
  import Cisco-IOS-XE-types {
    prefix ios-types;
  }
  import Cisco-IOS-XE-native {
    prefix ios;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Native Next Hop Resolution Protocol (NHRP) Yang model.
     Copyright (c) 2016, 2019 by Cisco Systems, Inc.
     All rights reserved.";

  revision 2019-07-02 {
    description
      "- Added config-llp-nhrp-grouping under interface Tunnel";
    cisco-semver:module-version "1.0.16120(m)";
  }
  revision 2019-07-01 {
    description
      "- Establish semantic version baseline
       - Support for all IPV4 and IPV6 NHRP commands under tunnel
       - Augmented Virtual-Template with nhrp";
    cisco-semver:module-version "1.0.0";
  }
  revision 2017-02-07 {
    description
      "Initial revision";
  }

  grouping config-interface-nhrp-common-grouping {
    leaf authentication {
      description
        "authentication string";
      type string;
    }
    container bfd {
      description
        "BFD Parameters";
      container notify {
        description
          "Set registration retry count for notification";
        leaf services {
          description
            "Retry counter for Services";
          type union {
            type enumeration {
              enum "never";
            }
            type uint8 {
              range "0..10";
            }
          }
        }
        leaf transport {
          description
            "Retry counter for Transport";
          type union {
            type enumeration {
              enum "never";
            }
            type uint8 {
              range "0..10";
            }
          }
        }
      }
      leaf strict-mode {
        description
          "Enable BFD in strict mode";
        type empty;
      }
    }
    container cache {
      description
        "NHRP Cache related commands.";
      leaf bgp-sync {
        description
          "Listen to BGP for endpoint creation and deletion.";
        type empty;
      }
      leaf non-authoritative {
        description
          "Mark cache entries non-authoritative";
        type empty;
      }
    }
    leaf connect {
      description
        "NHRP event request id";
      type uint16 {
        range "1..65535";
      }
    }
    leaf holdtime {
      description
        "Number of seconds";
      type uint16 {
        range "1..65535";
      }
    }
    container max-send {
      description
        "Rate limit NHRP traffic";
      list pkt-count {
        key "pkt-count";
        leaf pkt-count {
          description
            "Packet count";
          type uint16 {
            range "1..65535";
          }
        }
        leaf every {
          description
            "Interval in seconds";
          type uint16 {
            range "10..65535";
          }
        }
      }
    }
    container multicast {
      description
        "Multicast Parameters";
      choice batch-size-choice {
        container batch-size-default {
          description
            "Specify the batch size of Multicast replication";
          leaf batch-size {
            description
              "Batch Size";
            type empty;
          }
        }
        container batch-size-value {
          description
            "Specify batch interval to replicate Multicast Packets";
          leaf batch-size {
            description
              "Batch Size";
            type uint16 {
              range "1..65535";
            }
          }
          leaf batch-interval {
            description
              "Interval in milliseconds";
            type uint16 {
              range "1..65535";
            }
          }
        }
      }
    }
    leaf network-id {
      description
        "Network identifier";
      type uint32 {
        range "1..4294967295";
      }
    }
    container path {
      description
        "NHRP path specific configuration";
      container preference {
        description
          "Default preference for cache entries over this path";
        choice path-size-adaptive {
          case path-size-case {
            container pathsize {
              description
                "Default preference";
              leaf path-size {
                description
                  "Path preference (relative)";
                type uint16 {
                  range "1..255";
                }
              }
              leaf adaptive {
                description
                  "Adaptive path preference over this path";
                type empty;
              }
            }
          }
          case adaptive-case {
            leaf adaptive {
              description
                "Adaptive path preference over this path";
              type empty;
            }
          }
        }
      }
    }
    leaf record {
      description
        "Allow NHRP record option";
      type empty;
    }
    container redirect {
      description
        "Enable NHRP redirect traffic indication";
      presence "true";
      leaf timeout {
        description
          "Interval in seconds";
        type uint8 {
          range "2..30";
        }
      }
    }
    container reject {
      description
        "NHRP resolution reject request";
      list reqid {
        key "reqid";
        leaf reqid {
          description
            "reqid value";
          type uint16 {
            range "1..65535";
          }
        }
        leaf rej-secs {
          description
            "Number of seconds";
          type uint16 {
            range "0..65535";
          }
        }
      }
    }
    container responder {
      description
        "Responder interface";
      uses ios-ifc:interface-grouping;
    }
    leaf send-routed {
      description
        "Send NHRP packets via the routed path first";
      type empty;
    }
    container server-only {
      description
        "Disable NHRP requests";
      presence "true";
      leaf non-caching {
        description
          "Do not create NHRP cache entries";
        type empty;
      }
    }
    container shortcut {
      description
        "Enable shortcut switching";
      presence "true";
      leaf virtual-template {
        description
          "Virtual template number";
        type uint16 {
          range "1..4095";
        }
      }
    }
    container trigger-svc {
      description
        "Create NHRP cut-through based on traffic load";
      list kbps {
        key "kbps";
        leaf kbps {
          description
            "Trigger rate in kbps";
          type uint32 {
            range "1..4294967295";
          }
        }
        leaf tear-kbps {
          description
            "Teardown rate in kbps";
          type uint32 {
            range "0..4294967295";
          }
        }
      }
    }
    leaf use {
      description
        "Number of packets to cause NHRP request";
      type uint16 {
        range "1..65535";
      }
    }
  }

  grouping config-interface-ipv4-nhrp-grouping {
    container nhrp-v4 {
      container nhrp {
        description
          "NHRP interface subcommands";
        container attribute {
          description
            "NHRP attribute set";
          container set {
            description
              "attribute set";
            list attr-type {
              key "attr-type";
              leaf attr-type {
                description
                  "attribute type";
                type string;
              }
              leaf attr-val {
                description
                  "attribute value";
                type string;
              }
            }
          }
          leaf group {
            description
              "NHRP group name";
            type string;
          }
        }
        container interest {
          description
            "Specify an access list";
          leaf none {
            description
              "No traffic is interesting.";
            type empty;
          }
          leaf acl-range {
            description
              "IP access list";
            type uint8 {
              range "1..199";
            }
          }
        }
        container registration {
          description
            "Settings for registration packets.";
          leaf delay {
            description
              " Number of seconds to delay registration.";
            type uint8 {
              range "0..10";
            }
          }
          leaf no-unique {
            description
              "Do not set the 'Unique' flag in registration requests.";
            type empty;
          }
          leaf req-def-map {
            description
              "Request default map(s) in registration requests.";
            type empty;
          }
          leaf timeout {
            description
              "Number of seconds";
            type uint16 {
              range "1..65535";
            }
          }
        }
        container map {
          description
            "Map dest IP addresses to NBMA addresses";
          list dest-ipv4 {
            key "dest-ipv4";
            leaf dest-ipv4 {
              description
                "IP address of destination";
              type inet:ipv4-address;
            }
            list nbma-ipv4 {
              key "nbma-ipv4";
              leaf nbma-ipv4 {
                description
                  "IP NBMA address";
                type inet:ipv4-address;
              }
              list ipv4 {
                description
                  "IP NBMA address";
                key "ipv4-address";
                leaf ipv4-address {
                  type inet:ipv4-address;
                }
                leaf preference {
                  description
                    " Preference associated with the map";
                  type uint8 {
                    range "1..255";
                  }
                }
              }
              list ipv6 {
                description
                  "IPv6 NBMA address";
                key "ipv6-address";
                leaf ipv6-address {
                  type inet:ipv6-address;
                }
                leaf preference {
                  description
                    "Preference associated with the map";
                  type uint8 {
                    range "1..255";
                  }
                }
              }
              leaf preference {
                description
                  " Preference associated with the map";
                type uint8 {
                  range "1..255";
                }
              }
            }
            list dest-mask {
              key "dest-mask";
              leaf dest-mask {
                description
                  "IP mask of destination";
                type inet:ipv4-address;
              }
              list ipv4 {
                description
                  "IP NBMA address";
                key "ipv4-address";
                leaf ipv4-address {
                  type inet:ipv4-address;
                }
                leaf preference {
                  description
                    " Preference associated with the map";
                  type uint8 {
                    range "1..255";
                  }
                }
              }
              list ipv6 {
                description
                  "IPv6 NBMA address";
                key "ipv6-address";
                leaf ipv6-address {
                  type inet:ipv6-address;
                }
                leaf preference {
                  description
                    " Preference associated with the map";
                  type uint8 {
                    range "1..255";
                  }
                }
              }
              leaf preference {
                description
                  " Preference associated with the map";
                type uint8 {
                  range "1..255";
                }
              }
            }
            list nbma-ipv6 {
              key "nbma-ipv6";
              leaf nbma-ipv6 {
                description
                  " IPv6 NBMA address";
                type inet:ipv6-address;
              }
              leaf preference {
                description
                  " Preference associated with the map";
                type uint8 {
                  range "1..255";
                }
              }
            }
          }
          container multicast {
            description
              "Use this NBMA mapping for broadcasts/multicasts";
            leaf-list nbma_ipv4 {
              type inet:ipv4-address;
            }
            leaf-list nbma_ipv6 {
              type inet:ipv6-address;
            }
            leaf dynamic {
              description
                "Dynamically learn destinations from client registrations on hub";
              type empty;
            }
          }
        }
        container nhs {
          description
            "Specify a next hop server";
          list ipv4 {
            key "ipv4";
            leaf ipv4 {
              description
                "Protocol IP address of NHS";
              type inet:ipv4-address;
            }
            leaf cluster {
              description
                "NHS cluster number";
              type uint8 {
                range "0..10";
              }
            }
            container nbma {
              description
                "NBMA of NHS";
              list ipv4 {
                key "ipv4";
                leaf ipv4 {
                  description
                    "IPv4 address";
                  type inet:ipv4-address;
                }
                leaf cluster {
                  description
                    "NHS cluster number";
                  type uint8 {
                    range "0..10";
                  }
                }
                container multicast {
                  description
                    "Use this NBMA mapping for broadcasts/multicasts";
                  presence "true";
                  leaf cluster {
                    description
                      "NHS cluster number";
                    type uint8 {
                      range "0..10";
                    }
                  }
                  container priority {
                    description
                      "NHS priority, don't specify for default priority";
                    list prior {
                      key "prior";
                      leaf prior {
                        description
                          "NHS priority, range = 0 to 255, 0 is the highest";
                        type uint8 {
                          range "0..255";
                        }
                      }
                      leaf cluster {
                        description
                          "NHS cluster number";
                        type uint8 {
                          range "0..10";
                        }
                      }
                    }
                  }
                }
                container priority {
                  description
                    "NHS priority, don't specify for default priority";
                  list pri {
                    key "pri";
                    leaf pri {
                      description
                        "NHS priority, range = 0 to 255, 0 is the highest";
                      type uint8 {
                        range "0..255";
                      }
                    }
                    leaf cluster {
                      description
                        "NHS cluster number";
                      type uint8 {
                        range "0..10";
                      }
                    }
                  }
                }
              }
              list nhs-fqdn {
                key "nhs-fqdn";
                leaf nhs-fqdn {
                  description
                    "NHS FQDN string";
                  type string;
                }
                leaf cluster {
                  description
                    "NHS cluster number";
                  type uint8 {
                    range "0..10";
                  }
                }
                container multicast {
                  description
                    "Use this NBMA mapping for broadcasts/multicasts";
                  presence "true";
                  leaf cluster {
                    description
                      "NHS cluster number";
                    type uint8 {
                      range "0..10";
                    }
                  }
                  container priority {
                    description
                      "NHS priority, don't specify for default priority";
                    list mc-pri {
                      key "mc-pri";
                      leaf mc-pri {
                        description
                          "NHS priority, range = 0 to 255, 0 is the highest";
                        type uint8 {
                          range "0..255";
                        }
                      }
                      leaf cluster {
                        description
                          "NHS cluster number";
                        type uint8 {
                          range "0..10";
                        }
                      }
                    }
                  }
                }
                container priority {
                  description
                    "NHS priority, don't specify for default priority";
                  list nhs-pri {
                    key "nhs-pri";
                    leaf nhs-pri {
                      description
                        "NHS priority, range = 0 to 255, 0 is the highest";
                      type uint8 {
                        range "0..255";
                      }
                    }
                    leaf cluster {
                      description
                        "NHS cluster number";
                      type uint8 {
                        range "0..10";
                      }
                    }
                  }
                }
              }
              list ipv6 {
                key "ipv6";
                leaf ipv6 {
                  description
                    "IPv6 address";
                  type inet:ipv6-address;
                }
                leaf cluster {
                  description
                    "NHS cluster number";
                  type uint8 {
                    range "0..10";
                  }
                }
                container multicast {
                  description
                    "Use this NBMA mapping for broadcasts/multicasts";
                  presence "true";
                  leaf cluster {
                    description
                      "NHS cluster number";
                    type uint8 {
                      range "0..10";
                    }
                  }
                  container priority {
                    description
                      "NHS priority, don't specify for default priority";
                    list mc-pri {
                      key "mc-pri";
                      leaf mc-pri {
                        description
                          "NHS priority, range = 0 to 255, 0 is the highest";
                        type uint8 {
                          range "0..255";
                        }
                      }
                      leaf cluster {
                        description
                          "NHS cluster number";
                        type uint8 {
                          range "0..10";
                        }
                      }
                    }
                  }
                }
                container priority {
                  description
                    "NHS priority, don't specify for default priority";
                  list mc-prior {
                    key "mc-prior";
                    leaf mc-prior {
                      description
                        "NHS priority, range = 0 to 255, 0 is the highest";
                      type uint8 {
                        range "0..255";
                      }
                    }
                    leaf cluster {
                      description
                        "NHS cluster number";
                      type uint8 {
                        range "0..10";
                      }
                    }
                  }
                }
              }
            }
            container priority {
              description
                "NHS priority, don't specify for default priority";
              list pri-range {
                key "pri-range";
                leaf pri-range {
                  description
                    "NHS priority, range = 0 to 255, 0 is the highest";
                  type uint8 {
                    range "0..255";
                  }
                }
                leaf cluster {
                  description
                    "NHS cluster number";
                  type uint8 {
                    range "0..10";
                  }
                }
              }
            }
          }
          container cluster {
            description
              "NHS Redundancy cluster configurations";
            list clus-num {
              key "clus-num";
              leaf clus-num {
                description
                  "NHS cluster number";
                type uint8 {
                  range "0..10";
                }
              }
              leaf max-connections {
                description
                  "Max-connections value";
                type uint8 {
                  range "0..255";
                }
              }
            }
          }
          container dynamic {
            description
              "NHS protocol address dynamically learnt";
            container nbma {
              description
                "NBMA of NHS";
              list ipv4 {
                description
                  "NBMA of NHS";
                key "ipv4";
                leaf ipv4 {
                  description
                    "IPv4 address";
                  type inet:ipv4-address;
                }
                leaf cluster {
                  description
                    "NHS cluster number";
                  type uint8 {
                    range "0..10";
                  }
                }
                container multicast {
                  description
                    "Use this NBMA mapping for broadcasts/multicasts";
                  presence "true";
                  leaf cluster {
                    description
                      "NHS cluster number";
                    type uint8 {
                      range "0..10";
                    }
                  }
                  container priority {
                    description
                      "NHS priority, don't specify for default priority";
                    list dyn-pri {
                      key "dyn-pri";
                      leaf dyn-pri {
                        description
                          "NHS priority, range = 0 to 255, 0 is the highest";
                        type uint8 {
                          range "0..255";
                        }
                      }
                      leaf cluster {
                        description
                          "NHS cluster number";
                        type uint8 {
                          range "0..10";
                        }
                      }
                    }
                  }
                }
                container priority {
                  description
                    "NHS priority, don't specify for default priority";
                  list n-prior {
                    key "n-prior";
                    leaf n-prior {
                      description
                        "NHS priority, range = 0 to 255, 0 is the highest";
                      type uint8 {
                        range "0..255";
                      }
                    }
                    leaf cluster {
                      description
                        "NHS cluster number";
                      type uint8 {
                        range "0..10";
                      }
                    }
                  }
                }
              }
              list dyn-fqdn {
                key "dyn-fqdn";
                leaf dyn-fqdn {
                  description
                    "NHS FQDN string";
                  type string;
                }
                leaf cluster {
                  description
                    "NHS cluster number";
                  type uint8 {
                    range "0..10";
                  }
                }
                container multicast {
                  description
                    "Use this NBMA mapping for broadcasts/multicasts";
                  presence "true";
                  leaf cluster {
                    description
                      "NHS cluster number";
                    type uint8 {
                      range "0..10";
                    }
                  }
                  container priority {
                    description
                      "NHS priority, don't specify for default priority";
                    list dyn-mc-pri {
                      key "dyn-mc-pri";
                      leaf dyn-mc-pri {
                        description
                          "NHS priority, range = 0 to 255, 0 is the highest";
                        type uint8 {
                          range "0..255";
                        }
                      }
                      leaf cluster {
                        description
                          "NHS cluster number";
                        type uint8 {
                          range "0..10";
                        }
                      }
                    }
                  }
                }
                container priority {
                  description
                    "NHS priority, don't specify for default priority";
                  list dp {
                    key "dp";
                    leaf dp {
                      description
                        "NHS priority, range = 0 to 255, 0 is the highest";
                      type uint8 {
                        range "0..255";
                      }
                    }
                    leaf cluster {
                      description
                        "NHS cluster number";
                      type uint8 {
                        range "0..10";
                      }
                    }
                  }
                }
              }
              list ipv6 {
                key "ipv6";
                leaf ipv6 {
                  description
                    "IPv6 address";
                  type inet:ipv6-address;
                }
                leaf cluster {
                  description
                    "NHS cluster number";
                  type uint8 {
                    range "0..10";
                  }
                }
                container multicast {
                  description
                    "Use this NBMA mapping for broadcasts/multicasts";
                  presence "true";
                  leaf cluster {
                    description
                      "NHS cluster number";
                    type uint8 {
                      range "0..10";
                    }
                  }
                  container priority {
                    description
                      "NHS priority, don't specify for default priority";
                    list v6-pri {
                      key "v6-pri";
                      leaf v6-pri {
                        description
                          "NHS priority, range = 0 to 255, 0 is the highest";
                        type uint8 {
                          range "0..255";
                        }
                      }
                      leaf cluster {
                        description
                          "NHS cluster number";
                        type uint8 {
                          range "0..10";
                        }
                      }
                    }
                  }
                }
                container priority {
                  description
                    "NHS priority, don't specify for default priority";
                  list v6-pri2 {
                    key "v6-pri2";
                    leaf v6-pri2 {
                      description
                        "NHS priority, range = 0 to 255, 0 is the highest";
                      type uint8 {
                        range "0..255";
                      }
                    }
                    leaf cluster {
                      description
                        "NHS cluster number";
                      type uint8 {
                        range "0..10";
                      }
                    }
                  }
                }
              }
            }
          }
          leaf fallback {
            description
              "NHS Redundancy Fallback time, 0 -60 seconds";
            type uint8 {
              range "0..60";
            }
          }
        }
        container summary-map {
          description
            "Summary IP address";
          list dest-ipv4 {
            key "dest-ipv4";
            leaf dest-ipv4 {
              description
                "IP address";
              type inet:ipv4-address;
            }
            list dest-mask {
              key "dest-mask";
              leaf dest-mask {
                description
                  "mask destination";
                type inet:ipv4-address;
              }
              list nbma-ipv4 {
                key "nbma-ipv4";
                leaf nbma-ipv4 {
                  description
                    "IP NBMA address";
                  type inet:ipv4-address;
                }
                uses summary-map-grouping;
                container multicast {
                  description
                    "Use this NBMA mapping for broadcasts/multicasts";
                  presence "true";
                  uses summary-map-grouping;
                }
                container preference {
                  description
                    "Preference associated with the map";
                  list pri-range {
                    key "pri-range";
                    leaf pri-range {
                      description
                        "NHS priority, range = 1 to 255, 0 is the highest";
                      type uint8 {
                        range "1..255";
                      }
                    }
                    uses summary-map-grouping;
                    container multicast {
                      description
                        "Use this NBMA mapping for broadcasts/multicasts";
                      presence "true";
                      uses summary-map-grouping;
                    }
                  }
                  uses summary-map-grouping;
                  container multicast {
                    description
                      "Use this NBMA mapping for broadcasts/multicasts";
                    presence "true";
                    uses summary-map-grouping;
                  }
                }
              }
              list nbma-ipv6 {
                key "nbma-ipv6";
                leaf nbma-ipv6 {
                  description
                    "IPv6 NBMA address";
                  type inet:ipv6-address;
                }
                uses summary-map-grouping;
                container multicast {
                  description
                    "Use this NBMA mapping for broadcasts/multicasts";
                  presence "true";
                  uses summary-map-grouping;
                }
                container preference {
                  description
                    "Preference associated with the map";
                  list pri-range {
                    key "pri-range";
                    leaf pri-range {
                      description
                        "NHS priority, range = 1 to 255, 0 is the highest";
                      type uint8 {
                        range "1..255";
                      }
                    }
                    uses summary-map-grouping;
                    container multicast {
                      description
                        "Use this NBMA mapping for broadcasts/multicasts";
                      presence "true";
                      uses summary-map-grouping;
                    }
                  }
                  uses summary-map-grouping;
                  container multicast {
                    description
                      "Use this NBMA mapping for broadcasts/multicasts";
                    presence "true";
                    uses summary-map-grouping;
                  }
                }
              }
              leaf resolve {
                description
                  "Resolve mapping information for this summary";
                type empty;
              }
            }
          }
          list length-ipv4 {
            key "prefix";
            leaf prefix {
              description
                "IP address/<length> of destination, eg:24.6.0.0/16";
              type inet:ipv4-prefix;
            }
            list nbma-ipv4 {
              key "nbma-ipv4";
              leaf nbma-ipv4 {
                description
                  "IP NBMA address";
                type inet:ipv4-address;
              }
              uses summary-map-grouping;
              container multicast {
                description
                  "Use this NBMA mapping for broadcasts/multicasts";
                presence "true";
                uses summary-map-grouping;
              }
              container preference {
                description
                  "Preference associated with the map";
                list pri-range {
                  key "pri-range";
                  leaf pri-range {
                    description
                      "NHS priority, range = 1 to 255, 0 is the highest";
                    type uint8 {
                      range "1..255";
                    }
                  }
                  uses summary-map-grouping;
                  container multicast {
                    description
                      "Use this NBMA mapping for broadcasts/multicasts";
                    presence "true";
                    uses summary-map-grouping;
                  }
                }
                uses summary-map-grouping;
                container multicast {
                  description
                    "Use this NBMA mapping for broadcasts/multicasts";
                  presence "true";
                  uses summary-map-grouping;
                }
              }
            }
            list nbma-ipv6 {
              key "nbma-ipv6";
              leaf nbma-ipv6 {
                description
                  "IPv6 NBMA address";
                type inet:ipv6-address;
              }
              uses summary-map-grouping;
              container multicast {
                description
                  "Use this NBMA mapping for broadcasts/multicasts";
                presence "true";
                uses summary-map-grouping;
              }
              container preference {
                description
                  "Preference associated with the map";
                list pri-range {
                  key "pri-range";
                  leaf pri-range {
                    description
                      "NHS priority, range = 1 to 255, 0 is the highest";
                    type uint8 {
                      range "1..255";
                    }
                  }
                  uses summary-map-grouping;
                  container multicast {
                    description
                      "Use this NBMA mapping for broadcasts/multicasts";
                    presence "true";
                    uses summary-map-grouping;
                  }
                }
                uses summary-map-grouping;
                container multicast {
                  description
                    "Use this NBMA mapping for broadcasts/multicasts";
                  presence "true";
                  uses summary-map-grouping;
                }
              }
            }
            leaf resolve {
              description
                "Resolve mapping information for this summary";
              type empty;
            }
          }
        }
        uses config-interface-nhrp-common-grouping;
      }
    }
  }

  grouping config-interface-ipv6-nhrp-grouping {
    container nhrp {
      description
        "NHRP interface subcommands";
      container attribute {
        description
          "NHRP attribute set";
        container set {
          description
            "attribute set";
          list attr-type {
            key "attr-type";
            leaf attr-type {
              description
                "attribute type";
              type string;
            }
            leaf attr-val {
              description
                "attribute value";
              type string;
            }
          }
        }
      }
      container interest {
        description
          "Specify an access list";
        leaf none {
          description
            "No traffic is interesting.";
          type empty;
        }
        leaf acl-range {
          description
            "IP access list";
          type string;
        }
      }
      container map {
        description
          "Map dest IP addresses to NBMA addresses";
        list ipv6_nn {
          key "ipv6_nn";
          leaf ipv6_nn {
            description
              "IP prefix <network>/<length>";
            type ios-types:ipv6-prefix;
          }
          list ipv4 {
            description
              "IP NBMA address";
            key "ipv4-address";
            leaf ipv4-address {
              description
                "IPv4 NBMA address";
              type inet:ipv4-address;
            }
            leaf preference {
              description
                " Preference associated with the map";
              type uint8 {
                range "1..255";
              }
            }
          }
          list ipv6 {
            description
              "IPv6 NBMA address";
            key "ipv6-address";
            leaf ipv6-address {
              description
                "IPv6 NBMA address";
              type inet:ipv6-address;
            }
            leaf preference {
              description
                "Preference associated with the map";
              type uint8 {
                range "1..255";
              }
            }
          }
        }
      }
      container nhs {
        description
          "Specify a next hop server";
        list ipv6 {
          key "ipv6";
          leaf ipv6 {
            description
              "Protocol IP address of NHS";
            type inet:ipv6-address;
          }
          leaf cluster {
            description
              "NHS cluster number";
            type uint8 {
              range "0..10";
            }
          }
          container nbma {
            description
              "NBMA of NHS";
            list ipv4 {
              key "ipv4";
              leaf ipv4 {
                description
                  "IPv4 address";
                type inet:ipv4-address;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list prior {
                    key "prior";
                    leaf prior {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list pri {
                  key "pri";
                  leaf pri {
                    description
                      "NHS priority, range = 0 to 255, 0 is the highest";
                    type uint8 {
                      range "0..255";
                    }
                  }
                  leaf cluster {
                    description
                      "NHS cluster number";
                    type uint8 {
                      range "0..10";
                    }
                  }
                }
              }
            }
            list nhs-fqdn {
              key "nhs-fqdn";
              leaf nhs-fqdn {
                description
                  "NHS FQDN string";
                type string;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list mc-pri {
                    key "mc-pri";
                    leaf mc-pri {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list nhs-pri {
                  key "nhs-pri";
                  leaf nhs-pri {
                    description
                      "NHS priority, range = 0 to 255, 0 is the highest";
                    type uint8 {
                      range "0..255";
                    }
                  }
                  leaf cluster {
                    description
                      "NHS cluster number";
                    type uint8 {
                      range "0..10";
                    }
                  }
                }
              }
            }
            list ipv6 {
              key "ipv6";
              leaf ipv6 {
                description
                  "IPv6 address";
                type inet:ipv6-address;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list mc-pri {
                    key "mc-pri";
                    leaf mc-pri {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list mc-prior {
                  key "mc-prior";
                  leaf mc-prior {
                    description
                      "NHS priority, range = 0 to 255, 0 is the highest";
                    type uint8 {
                      range "0..255";
                    }
                  }
                  leaf cluster {
                    description
                      "NHS cluster number";
                    type uint8 {
                      range "0..10";
                    }
                  }
                }
              }
            }
          }
          container priority {
            description
              "NHS priority, don't specify for default priority";
            list pri-range {
              key "pri-range";
              leaf pri-range {
                description
                  "NHS priority, range = 0 to 255, 0 is the highest";
                type uint8 {
                  range "0..255";
                }
              }
              leaf cluster {
                description
                  "NHS cluster number";
                type uint8 {
                  range "0..10";
                }
              }
            }
          }
        }
        container cluster {
          description
            "NHS Redundancy cluster configurations";
          list clus-num {
            key "clus-num";
            leaf clus-num {
              description
                "NHS cluster number";
              type uint8 {
                range "0..10";
              }
            }
            leaf max-connections {
              description
                "Max-connections value";
              type uint8 {
                range "0..255";
              }
            }
          }
        }
        container dynamic {
          description
            "NHS protocol address dynamically learnt";
          container nbma {
            description
              "NBMA of NHS";
            list ipv4 {
              description
                "NBMA of NHS";
              key "ipv4";
              leaf ipv4 {
                description
                  "IPv4 address";
                type inet:ipv4-address;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list dyn-pri {
                    key "dyn-pri";
                    leaf dyn-pri {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list n-prior {
                  key "n-prior";
                  leaf n-prior {
                    description
                      "NHS priority, range = 0 to 255, 0 is the highest";
                    type uint8 {
                      range "0..255";
                    }
                  }
                  leaf cluster {
                    description
                      "NHS cluster number";
                    type uint8 {
                      range "0..10";
                    }
                  }
                }
              }
            }
            list dyn-fqdn {
              key "dyn-fqdn";
              leaf dyn-fqdn {
                description
                  "NHS FQDN string";
                type string;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list dyn-mc-pri {
                    key "dyn-mc-pri";
                    leaf dyn-mc-pri {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list dp {
                  key "dp";
                  leaf dp {
                    description
                      "NHS priority, range = 0 to 255, 0 is the highest";
                    type uint8 {
                      range "0..255";
                    }
                  }
                  leaf cluster {
                    description
                      "NHS cluster number";
                    type uint8 {
                      range "0..10";
                    }
                  }
                }
              }
            }
            list ipv6 {
              key "ipv6";
              leaf ipv6 {
                description
                  "IPv6 address";
                type inet:ipv6-address;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list v6-pri {
                    key "v6-pri";
                    leaf v6-pri {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list v6-pri2 {
                  key "v6-pri2";
                  leaf v6-pri2 {
                    description
                      "NHS priority, range = 0 to 255, 0 is the highest";
                    type uint8 {
                      range "0..255";
                    }
                  }
                  leaf cluster {
                    description
                      "NHS cluster number";
                    type uint8 {
                      range "0..10";
                    }
                  }
                }
              }
            }
          }
        }
        leaf fallback {
          description
            "NHS Redundancy Fallback time, 0 -60 seconds";
          type uint8 {
            range "0..60";
          }
        }
      }
      container registration {
        description
          "Settings for registration packets.";
        leaf delay {
          description
            " Number of seconds to delay registration.";
          type uint8 {
            range "0..10";
          }
        }
        leaf no-unique {
          description
            "Do not set the 'Unique' flag in registration requests.";
          type empty;
        }
        leaf timeout {
          description
            "Number of seconds";
          type uint16 {
            range "1..65535";
          }
        }
      }
      container summary-map {
        description
          "Summary IP address";
        list ipv6-nn {
          key "ipv6-nn";
          leaf ipv6-nn {
            description
              "IP prefix <network>/<length>";
            type ios-types:ipv6-prefix;
          }
          list nbma-ipv4 {
            key "nbma-ipv4";
            leaf nbma-ipv4 {
              description
                "IP NBMA address";
              type inet:ipv4-address;
            }
            container preference {
              description
                "Preference associated with the map";
              list pri-range {
                key "pri-range";
                leaf pri-range {
                  description
                    "NHS priority, range = 1 to 255, 0 is the highest";
                  type uint8 {
                    range "1..255";
                  }
                }
                uses summary-map-grouping;
                container multicast {
                  description
                    "Use this NBMA mapping for broadcasts/multicasts";
                  presence "true";
                  uses summary-map-grouping;
                }
              }
              uses summary-map-grouping;
              container multicast {
                description
                  "Use this NBMA mapping for broadcasts/multicasts";
                presence "true";
                uses summary-map-grouping;
              }
            }
          }
          list nbma-ipv6 {
            key "nbma-ipv6";
            leaf nbma-ipv6 {
              description
                "IPv6 NBMA address";
              type inet:ipv6-address;
            }
            container preference {
              description
                "Preference associated with the map";
              list pri-range {
                key "pri-range";
                leaf pri-range {
                  description
                    "NHS priority, range = 1 to 255, 0 is the highest";
                  type uint8 {
                    range "1..255";
                  }
                }
                uses summary-map-grouping;
                container multicast {
                  description
                    "Use this NBMA mapping for broadcasts/multicasts";
                  presence "true";
                  uses summary-map-grouping;
                }
              }
              uses summary-map-grouping;
              container multicast {
                description
                  "Use this NBMA mapping for broadcasts/multicasts";
                presence "true";
                uses summary-map-grouping;
              }
            }
          }
          leaf resolve {
            description
              "Resolve mapping information for this summary";
            type empty;
          }
        }
      }
      uses config-interface-nhrp-common-grouping;
    }
  }

  grouping config-tunnel-if-state-grouping {
    container if-state-tunnel {
      container if-state {
        description
          "Allow applications to control interface state";
        leaf nhrp {
          description
            "Allow NHRP to control interface state";
          type empty;
        }
        leaf track {
          description
            "Track an object";
          type uint16 {
            range "1..1000";
          }
        }
      }
    }
  }

  grouping config-interface-tunn-grouping {
    container nhrp-tunn {
      container nhrp {
        description
          "NHRP Interface commands";
        container attribute {
          description
            "NHRP attribute";
          leaf group {
            description
              "NHRP group name";
            type string;
          }
        }
        container event-publisher {
          description
            "Enable NHRP smart spoke feature";
          leaf max-event-timeout {
            description
              "Number of seconds";
            type uint8 {
              range "1..22";
            }
          }
        }
        leaf group {
          description
            "group name string";
          type string;
        }
        container map {
          description
            "Map group name to QoS service policy";
          container group {
            description
              "NHRP group mapping";
            list nhrp-name {
              key "nhrp-name";
              leaf nhrp-name {
                description
                  "NHRP group name";
                type string;
              }
              container service-policy {
                description
                  "QoS service-policy";
                leaf output {
                  description
                    "QoS policy-map name";
                  type string;
                }
              }
            }
          }
        }
        leaf route-watch {
          description
            "Enable NHRP route watch";
          type empty;
        }
      }
    }
  }

  grouping summary-map-grouping {
    container match {
      description
        "Use this NBMA mapping based on match criteria";
      container attribute {
        description
          "Select map based on a user defined attribute";
        list attr-type {
          key "attr-type";
          leaf attr-type {
            description
              "attribute type";
            type string;
          }
          leaf attr-val {
            description
              "attribute value";
            type string;
          }
        }
      }
      leaf geo-location {
        description
          "Select map based on geographical location";
        type string;
      }
      leaf group {
        description
          "Select map based on group";
        type string;
      }
      leaf topo-location {
        description
          "Select map based on topological location";
        type string;
      }
    }
  }

  grouping config-global-nhrp-grouping {
    container nhrp {
      description
        "NHRP global commands";
      when "/ios:native/ios:service/ios:internal";
      container G-Ach {
        description
          " Generic Associated Channel ";
        leaf type {
          description
            "G-ACh type";
          type uint32 {
            range "0..32767";
          }
        }
      }
      container multicast {
        description
          "NHRP multicast related commands";
        container queue {
          description
            " Incoming multicast packet queue ";
          leaf size {
            description
              "Size of the queue";
            type uint32 {
              range "512..10240";
            }
          }
          leaf threshold {
            description
              "Threshold beyond which non-locally generated packets are dropped";
            type uint32 {
              range "0..10240";
            }
          }
        }
      }
    }
  }

  grouping config-interface-nhrp-grouping {
    container nhrp {
      description
        "NHRP interface subcommands";
      status obsolete;
      container attribute {
        description
          "NHRP attribute set";
        container set {
          description
            "attribute set";
          list attr-type {
            key "attr-type";
            leaf attr-type {
              description
                "attribute type";
              type string;
            }
            leaf attr-val {
              description
                "attribute value";
              type string;
            }
          }
        }
      }
      leaf authentication {
        description
          "authentication string";
        type string;
      }
      container cache {
        description
          "NHRP Cache related commands.";
        leaf non-authoritative {
          description
            "Mark cache entries non-authoritative";
          type empty;
        }
      }
      leaf connect {
        description
          "NHRP event request id";
        type uint16 {
          range "1..65535";
        }
      }
      leaf group {
        type string;
      }
      leaf holdtime {
        description
          "Number of seconds";
        type uint16 {
          range "1..65535";
        }
      }
      container interest {
        description
          "Specify an access list";
        leaf acl-range {
          description
            "IP access list";
          type uint8 {
            range "1..199";
          }
        }
        leaf none {
          description
            "No traffic is interesting.";
          type empty;
        }
      }
      container map {
        description
          "Map dest IP addresses to NBMA addresses";
        list dest-ipv4 {
          key "dest-ipv4";
          leaf dest-ipv4 {
            description
              "IP address of destination";
            type inet:ipv4-address;
          }
          list nbma-ipv4 {
            key "nbma-ipv4";
            leaf nbma-ipv4 {
              description
                "IP NBMA address";
              type inet:ipv4-address;
            }
            leaf ipv4 {
              type inet:ipv4-address;
            }
            leaf ipv6 {
              type inet:ipv6-address;
            }
          }
          list dest-mask {
            key "dest-mask";
            leaf dest-mask {
              description
                "IP mask of destination";
              type inet:ipv4-address;
            }
            leaf ipv4 {
              type inet:ipv4-address;
            }
            leaf ipv6 {
              type inet:ipv6-address;
            }
          }
          leaf nbma-ipv6 {
            type inet:ipv6-address;
          }
        }
        container multicast {
          description
            "Use this NBMA mapping for broadcasts/multicasts";
          leaf-list nbma_ipv4 {
            type inet:ipv4-address;
          }
          leaf-list nbma_ipv6 {
            type inet:ipv6-address;
          }
          leaf dynamic {
            description
              "Dynamically learn destinations from client registrations on hub";
            type empty;
          }
        }
        list group {
          key "name";
          leaf name {
            type string;
          }
          container service-policy {
            leaf output {
              description
                "Policy";
              type string;
            }
          }
        }
      }
      container max-send {
        description
          "Rate limit NHRP traffic";
        list pkt-count {
          key "pkt-count";
          leaf pkt-count {
            description
              "Packet count";
            type uint16 {
              range "1..65535";
            }
          }
          leaf every {
            description
              "Interval in seconds";
            type uint16 {
              range "10..65535";
            }
          }
        }
      }
      leaf network-id {
        description
          "Network identifier";
        type uint32 {
          range "1..4294967295";
        }
      }
      container nhs {
        description
          "Specify a next hop server";
        list ipv4 {
          key "ipv4";
          leaf ipv4 {
            description
              "Protocol IP address of NHS";
            type inet:ipv4-address;
          }
          leaf cluster {
            description
              "NHS cluster number";
            type uint8 {
              range "0..10";
            }
          }
          container nbma {
            description
              "NBMA of NHS";
            list ipv4 {
              key "ipv4";
              leaf ipv4 {
                description
                  "IPv4 address";
                type inet:ipv4-address;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list prior {
                    key "prior";
                    leaf prior {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list pri {
                  key "pri";
                  leaf pri {
                    description
                      "NHS priority, range = 0 to 255, 0 is the highest";
                    type uint8 {
                      range "0..255";
                    }
                  }
                  leaf cluster {
                    description
                      "NHS cluster number";
                    type uint8 {
                      range "0..10";
                    }
                  }
                }
              }
            }
            list nhs-fqdn {
              key "nhs-fqdn";
              leaf nhs-fqdn {
                description
                  "NHS FQDN string";
                type string;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list mc-pri {
                    key "mc-pri";
                    leaf mc-pri {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list nhs-pri {
                  key "nhs-pri";
                  leaf nhs-pri {
                    description
                      "NHS priority, range = 0 to 255, 0 is the highest";
                    type uint8 {
                      range "0..255";
                    }
                  }
                  leaf cluster {
                    description
                      "NHS cluster number";
                    type uint8 {
                      range "0..10";
                    }
                  }
                }
              }
            }
            list ipv6 {
              key "ipv6";
              leaf ipv6 {
                description
                  "IPv6 address";
                type inet:ipv6-address;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list mc-pri {
                    key "mc-pri";
                    leaf mc-pri {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list mc-prior {
                  key "mc-prior";
                  leaf mc-prior {
                    description
                      "NHS priority, range = 0 to 255, 0 is the highest";
                    type uint8 {
                      range "0..255";
                    }
                  }
                  leaf cluster {
                    description
                      "NHS cluster number";
                    type uint8 {
                      range "0..10";
                    }
                  }
                }
              }
            }
          }
          container priority {
            description
              "NHS priority, don't specify for default priority";
            list pri-range {
              key "pri-range";
              leaf pri-range {
                description
                  "NHS priority, range = 0 to 255, 0 is the highest";
                type uint8 {
                  range "0..255";
                }
              }
              leaf cluster {
                description
                  "NHS cluster number";
                type uint8 {
                  range "0..10";
                }
              }
            }
          }
        }
        container cluster {
          description
            "NHS Redundancy cluster configurations";
          list clus-num {
            key "clus-num";
            leaf clus-num {
              description
                "NHS cluster number";
              type uint8 {
                range "0..10";
              }
            }
            leaf max-connections {
              description
                "Max-connections value";
              type uint8 {
                range "0..255";
              }
            }
          }
        }
        container dynamic {
          description
            "NHS protocol address dynamically learnt";
          container nbma {
            description
              "NBMA of NHS";
            list ipv4 {
              description
                "NBMA of NHS";
              key "ipv4";
              leaf ipv4 {
                description
                  "IPv4 address";
                type inet:ipv4-address;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list dyn-pri {
                    key "dyn-pri";
                    leaf dyn-pri {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list n-prior {
                  key "n-prior";
                  leaf n-prior {
                    description
                      "NHS priority, range = 0 to 255, 0 is the highest";
                    type uint8 {
                      range "0..255";
                    }
                  }
                  leaf cluster {
                    description
                      "NHS cluster number";
                    type uint8 {
                      range "0..10";
                    }
                  }
                }
              }
            }
            list dyn-fqdn {
              key "dyn-fqdn";
              leaf dyn-fqdn {
                description
                  "NHS FQDN string";
                type string;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list dyn-mc-pri {
                    key "dyn-mc-pri";
                    leaf dyn-mc-pri {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list dp {
                  key "dp";
                  leaf dp {
                    description
                      "NHS priority, range = 0 to 255, 0 is the highest";
                    type uint8 {
                      range "0..255";
                    }
                  }
                  leaf cluster {
                    description
                      "NHS cluster number";
                    type uint8 {
                      range "0..10";
                    }
                  }
                }
              }
            }
            list ipv6 {
              key "ipv6";
              leaf ipv6 {
                description
                  "IPv6 address";
                type inet:ipv6-address;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list v6-pri {
                    key "v6-pri";
                    leaf v6-pri {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list v6-pri2 {
                  key "v6-pri2";
                  leaf v6-pri2 {
                    description
                      "NHS priority, range = 0 to 255, 0 is the highest";
                    type uint8 {
                      range "0..255";
                    }
                  }
                  leaf cluster {
                    description
                      "NHS cluster number";
                    type uint8 {
                      range "0..10";
                    }
                  }
                }
              }
            }
          }
        }
        leaf fallback {
          description
            "NHS Redundancy Fallback time, 0 -60 seconds";
          type uint8 {
            range "0..60";
          }
        }
      }
      leaf record {
        description
          "Allow NHRP record option";
        type empty;
      }
      container redirect {
        description
          "Enable NHRP redirect traffic indication";
        presence "true";
        leaf timeout {
          description
            "Interval in seconds";
          type uint8 {
            range "2..30";
          }
        }
      }
      container registration {
        description
          "Settings for registration packets.";
        leaf no-unique {
          description
            "Do not set the 'Unique' flag in registration requests.";
          type empty;
        }
        leaf timeout {
          description
            "Number of seconds";
          type uint16 {
            range "1..65535";
          }
        }
      }
      container reject {
        description
          "NHRP resolution reject request";
        list reqid {
          key "reqid";
          leaf reqid {
            description
              "reqid value";
            type uint16 {
              range "1..65535";
            }
          }
          leaf rej-secs {
            description
              "Number of seconds";
            type uint16 {
              range "0..65535";
            }
          }
        }
      }
      container responder {
        description
          "Responder interface";
        leaf res-int {
          description
            "Virtual ACR interface";
          type string;
        }
        leaf Analysis-Module {
          description
            "Analysis-Module interface number";
          type uint8;
        }
        leaf Fcpa {
          description
            "Fcpa interface number";
          type uint8;
        }
        leaf SBC {
          description
            "SBC interface number";
          type uint32 {
            range "0..2147483647";
          }
        }
        leaf SONET_ACR {
          description
            "SONET_ACR interface number";
          type uint8;
        }
        leaf TB-controller {
          description
            "Telecom-Bus Clock Controller";
          type string;
        }
        leaf Service-Engine {
          description
            "Service-Engine interface number";
          type uint8;
        }
        leaf Tunnel {
          description
            "Tunnel interface number";
          type uint32 {
            range "0..2147483647";
          }
        }
        leaf Tunnel-tp {
          description
            "Tunnel-tp interface number";
          type uint16 {
            range "0..65535";
          }
        }
        leaf VPN {
          description
            "VPN interface number";
          type uint32 {
            range "0..2147483647";
          }
        }
        leaf Virtual-TokenRing {
          description
            "Virtual-TokenRing interface number";
          type uint32 {
            range "0..2147483647";
          }
        }
        leaf VirtualPortGroup {
          description
            "VirtualPortGroup interface number";
          type uint8 {
            range "0..31";
          }
        }
        leaf Vlan {
          description
            "Vlan interface number";
          type uint16 {
            range "1..4095";
          }
        }
        leaf ucse {
          description
            "ucse interface number";
          type uint8;
        }
        leaf vasileft {
          description
            "vasileft interface number";
          type uint16 {
            range "1..2000";
          }
        }
        leaf vasiright {
          description
            "vasiright interface number";
          type uint16 {
            range "1..2000";
          }
        }
      }
      container server-only {
        description
          "Disable NHRP requests";
        presence "true";
        leaf non-caching {
          description
            "Do not create NHRP cache entries";
          type empty;
        }
      }
      container shortcut {
        description
          "Enable shortcut switching";
        presence "true";
        leaf virtual-template {
          description
            "Virtual template number";
          type uint16 {
            range "1..4095";
          }
        }
      }
      container trigger-svc {
        description
          "Create NHRP cut-through based on traffic load";
        list kbps {
          key "kbps";
          leaf kbps {
            description
              "Trigger rate in kbps";
            type uint32 {
              range "1..4294967295";
            }
          }
          leaf tear-kbps {
            description
              "Teardown rate in kbps";
            type uint32 {
              range "0..4294967295";
            }
          }
        }
      }
      leaf use {
        description
          "Number of packets to cause NHRP request";
        type uint16 {
          range "1..65535";
        }
      }
    }
  }

  grouping config-llp-nhrp-grouping {
    container llp {
      description
        "NHRP multicast map for link layer protocols";
      container nhrp {
        description
          "NHRP interface subcommands";
        container map {
          description
            "Map dest IP addresses to NBMA addresses";
          container multicast {
            description
              "Use this NBMA mapping for broadcasts/multicasts";
            list ipv4 {
              description
                "IP NBMA address";
              key "ipv4-address";
              leaf ipv4-address {
                type inet:ipv4-address;
              }
            }
            list ipv6 {
              description
                "IPv6 NBMA address";
              key "ipv6-address";
              leaf ipv6-address {
                type inet:ipv6-address;
              }
            }
            leaf dynamic {
              description
                "Dynamically learn destinations from client registrations on hub";
              type empty;
            }
          }
        }
      }
    }
  }

  augment "/ios:native/ios:interface/ios:Tunnel/ios:ip" {
    uses config-interface-nhrp-grouping;
  }
  augment "/ios:native/ios:interface/ios:Tunnel/ios:ip" {
    uses config-interface-ipv4-nhrp-grouping;
  }
  augment "/ios:native/ios:interface/ios:Virtual-Template/ios:ip" {
    when "/ios:native/ios:interface/ios:Virtual-Template/ios:type = 'tunnel'";
    uses config-interface-ipv4-nhrp-grouping;
  }
  augment "/ios:native/ios:interface/ios:Tunnel" {
    uses config-llp-nhrp-grouping;
  }
  augment "/ios:native/ios:interface/ios:Tunnel/ios:ipv6" {
    uses config-interface-ipv6-nhrp-grouping;
  }
  augment "/ios:native/ios:interface/ios:Virtual-Template/ios:ipv6" {
    when "/ios:native/ios:interface/ios:Virtual-Template/ios:type = 'tunnel'";
    uses config-interface-ipv6-nhrp-grouping;
  }
  augment "/ios:native/ios:interface/ios:Tunnel" {
    uses config-interface-tunn-grouping;
  }
  augment "/ios:native/ios:interface/ios:Virtual-Template" {
    when "/ios:native/ios:interface/ios:Virtual-Template/ios:type = 'tunnel'";
    uses config-interface-tunn-grouping;
  }
  augment "/ios:native/ios:interface/ios:Tunnel" {
    uses config-tunnel-if-state-grouping;
  }
  augment "/ios:native/ios:interface/ios:Virtual-Template" {
    uses config-tunnel-if-state-grouping;
  }
  augment "/ios:native" {
    uses config-global-nhrp-grouping;
  }
}
