module Cisco-IOS-XE-features {
  namespace "http://cisco.com/ns/yang/Cisco-IOS-XE-features";
  prefix ios-features;

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE feature Definitions
     Copyright (c) 2016-2018 by Cisco Systems, Inc.
     All rights reserved.";

  revision 2019-02-25 {
    description
      "Added iso-igrp feature";
  }
  revision 2018-11-20 {
    description
      "Added license-suite-command feature for license boot suite command";
  }
  revision 2017-02-07 {
    description
      "Initial revision";
  }

  feature switching-platform {
    description
      "switching platform specific features";
  }

  feature crypto {
    description
      "crypto feature";
  }

  feature device-tracking {
    description
      "device-tracking feature";
  }

  feature dhcp-border-relay {
    description
      "dhcp-border-relay feature";
  }

  feature dot1x {
    description
      "dot1x feature";
  }

  feature efp {
    description
      "Ethernet Flow Point (efp) feature";
  }

  feature esmc {
    description
      "Ethernet Synchronization Messaging Channel (esmc) feature";
  }

  feature eth-evc {
    description
      "Ethernet Virtual Circuit (EVC) feature";
  }

  feature ezpm {
    description
      "Easy Performance Monitor feature";
  }

  feature iso-igrp {
    description
      "ISO IGRP feature";
  }

  feature l2 {
    description
      "Layer2 VPN feature";
  }

  feature l2vpn {
    description
      "Layer2 VPN feature";
  }

  feature macsec {
    description
      "macsec";
  }

  feature mem-size {
    description
      "Memory size commands";
  }

  feature module {
    description
      "Device module feature";
  }

  feature multilink {
    description
      "PPP multilink global configuration";
  }

  feature mls {
    description
      "Multilayer Switching feature";
  }

  feature omp {
    description
      "Overlay Management Protocol (OMP) feature";
  }

  feature parameter-map {
    description
      "Parameter Map feature";
  }

  feature private-vlan {
    description
      "Private-vlan feature";
  }

  feature punt-num {
    description
      "Police punt feature";
  }

  feature qos-qsm {
    description
      "QoS queue softmax multiplier";
  }

  feature scada-gw {
    description
      "SCADA Gateway";
  }

  feature sdwan {
    description
      "sdwan feature";
  }

  feature license-suite-command {
    description
      "license boot suite feature";
  }

  feature setup {
    description
      "Express setup feature";
  }

  feature switch-virtual {
    description
      "Switch-virtual feature";
  }

  feature table-map {
    description
      "table-map feature";
  }

  feature tod-clock {
    description
      "Time of Day clock feature";
  }

  feature transceiver {
    description
      "Transceiver commands";
  }

  feature virtual-template {
    description
      "Virtual-template commands";
  }

  feature vlan {
    description
      "Vlan feature";
  }

  feature med {
    description
      "Media End-point Discovery";
  }
}
