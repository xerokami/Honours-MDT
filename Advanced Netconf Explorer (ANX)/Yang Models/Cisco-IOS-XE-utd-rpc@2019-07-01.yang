module Cisco-IOS-XE-utd-rpc {
  namespace "http://cisco.com/ns/yang/Cisco-IOS-XE-utd-rpc";
  prefix ios-xe-utd-rpc;

  import cisco-semver {
    prefix cisco-semver;
  }
  import Cisco-IOS-XE-rpc {
    prefix ios-xe-rpc;
  }

  organization
    "Cisco Systems";
  contact
    "<mailto:cs-yang@cisco.com>";
  description
    "NED UTD RPC YANG module for IOS
     Copyright (c) 2016-2019 by Cisco Systems, Inc.
     All rights reserved.";

  revision 2019-07-01 {
    description
      "- Establish semantic version baseline
       - Created for NED RPC modularisation";
    cisco-semver:module-version "1.0.0";
  }

  grouping utd-username-password-grouping {
    leaf username {
      description
        "Provide the username for authentication";
      mandatory true;
      type string;
    }
    leaf password {
      description
        "Provide the password for authentication";
      mandatory true;
      type string;
    }
  }

  rpc utd {
    description
      "Unified Threat Defense commands";
    input {
      choice feature {
        case feature-threat {
          container threat-inspection {
            description
              "IPS/IDS related commands";
            container signature {
              description
                "Provide actions to be taken for signatures";
              choice method {
                container saved-drop-node-name {
                  leaf update {
                    description
                      "Update the IPS/IDS signature rules";
                    mandatory true;
                    type empty;
                  }
                }
                container manual-drop-node-name {
                  container update {
                    description
                      "Update the IPS/IDS signature rules";
                    choice type {
                      container file {
                        description
                          "Perform an update of the signature package using a local file";
                        leaf filename-drop-node-name {
                          mandatory true;
                          type string;
                        }
                      }
                      container server {
                        description
                          "Provide config options for the signature update server";
                        choice type {
                          container cisco {
                            description
                              "Use Cisco site to provide updates";
                            uses utd-username-password-grouping;
                          }
                          container url {
                            description
                              "Enter the complete URL for the path to the update server";
                            choice url-uname-passwd {
                              container credentials-drop-node-name {
                                leaf url-drop-node-name {
                                  mandatory true;
                                  type string;
                                }
                                uses utd-username-password-grouping;
                              }
                              container no-credentials-drop-node-name {
                                leaf url-drop-node-name {
                                  mandatory true;
                                  type string;
                                }
                              }
                            }
                          }
                        }
                      }
                    }
                  }
                }
              }
            }
          }
        }
        case feature-webfltr {
          container web-filter {
            description
              "Web-filter related commands";
            container database {
              description
                "Provide actions to be taken for the web-filter database";
              leaf update {
                description
                  "Update the web-filter database";
                mandatory true;
                type empty;
              }
            }
          }
        }
        case feature-file-inspection {
          container file-inspection {
            description
              "UTD file inspection commands";
            container analysis {
              description
                "UTD file analysis related commands";
              leaf apikey {
                description
                  "Provide UTD file analysis apikey";
                mandatory true;
                type string {
                  length "1..128";
                }
              }
            }
          }
        }
      }
    }
    output {
      uses ios-xe-rpc:cisco-xe-rpc-output;
    }
  }
  augment "/ios-xe-rpc:clear/ios-xe-rpc:input/ios-xe-rpc:clear-choice" {
    case utd-case {
      container utd {
        description
          "Clear Unified Threat Defense information";
        container engine {
          description
            "Clear information about the UTD engine";
          container standard {
            description
              "Clear information about the standard engine";
            choice utd-eng-std-choice {
              container logging {
                description
                  "Clear logging information/logs from the container";
                leaf events {
                  description
                    "Clear engine logging events from the container";
                  type empty;
                }
              }
              container statistics {
                description
                  "Clear the engine statistics from the container";
                choice stats-choice {
                  container daq {
                    description
                      "Clear statistics for DAQ from the container";
                    choice daq-choice {
                      case all {
                        leaf all-drop-node-name {
                          type empty;
                        }
                      }
                      case vrf {
                        container vrf {
                          description
                            "Specify VRF for the stats";
                          choice vrf-choice {
                            case global {
                              leaf global {
                                description
                                  "Global VRF";
                                type empty;
                              }
                            }
                            case name {
                              leaf name {
                                description
                                  "VRF name";
                                type string {
                                  length "1..32";
                                }
                              }
                            }
                          }
                        }
                      }
                    }
                  }
                  container url-filtering {
                    description
                      "Clear statistics for url filtering from the container";
                    choice url-filtering-choice {
                      case all {
                        leaf all-drop-node-name {
                          type empty;
                        }
                      }
                      case vrf {
                        container vrf {
                          description
                            "Specify VRF for the stats";
                          choice vrf-choice {
                            case global {
                              leaf global {
                                description
                                  "Global VRF";
                                type empty;
                              }
                            }
                            case name {
                              leaf name {
                                description
                                  "VRF name";
                                type string {
                                  length "1..32";
                                }
                              }
                            }
                          }
                        }
                      }
                    }
                  }
                }
              }
            }
          }
        }
      }
    }
  }
  augment "/ios-xe-rpc:clear/ios-xe-rpc:input/ios-xe-rpc:clear-choice/ios-xe-rpc:platform-case/ios-xe-rpc:platform/ios-xe-rpc:hardware/ios-xe-rpc:qfp/ios-xe-rpc:active/ios-xe-rpc:feature/ios-xe-rpc:feature-choice" {
    case utd-case {
      container utd {
        description
          "Clear QFP UTD";
        container stats {
          description
            "Clear UTD statistics";
          choice stats-choice {
            case all {
              leaf all-drop-node-name {
                type empty;
              }
            }
            case default {
              container default {
                description
                  "Default Context";
                leaf context {
                  description
                    "Default Context";
                  type empty;
                }
              }
            }
            case divert {
              leaf divert {
                description
                  "Clear AppNav Redirect Statistics";
                type empty;
              }
            }
            case drop {
              leaf drop {
                description
                  "Clear Drop Statistics";
                type empty;
              }
            }
            case general {
              leaf general {
                description
                  "Clear General Statistics";
                type empty;
              }
            }
            case sn {
              leaf sn {
                description
                  "Clear AppNav Service Node Statistics";
                type empty;
              }
            }
            case summary {
              leaf summary {
                description
                  "Clear Summary Statistics";
                type empty;
              }
            }
            case vrf {
              container vrf {
                description
                  "Clear VRF Statistics";
                choice vrf-choice {
                  case default-context {
                    container default {
                      description
                        "Default Context";
                      leaf context {
                        description
                          "Default Context";
                        type empty;
                      }
                    }
                  }
                  case global {
                    leaf global {
                      description
                        "Global domain";
                      type empty;
                    }
                  }
                  case id {
                    leaf id {
                      description
                        "Clear VRF statistics by id";
                      type uint16 {
                        range "0..4096";
                      }
                    }
                  }
                  case name {
                    leaf name {
                      description
                        "Clear VRF statistics by name";
                      type string {
                        length "1..32";
                      }
                    }
                  }
                }
              }
            }
          }
        }
      }
    }
  }
}
